/*
 * Copyright (c) 2015 Huawei, Inc. and others. All rights reserved.
 *
 * This program and the accompanying materials are made available under the
 * terms of the Eclipse Public License v1.0 which accompanies this distribution,
 * and is available at http://www.eclipse.org/legal/epl-v10.html
 */

module nemo-object {
    yang-version 1;

    namespace "urn:opendaylight:params:xml:ns:yang:nemo:object";
    prefix "nemo-object";

    import nemo-common {prefix nemo-common;}

    revision "2015-10-10" {
        description
            "Initial revision.";
    }

    grouping property-definitions {
        list property-definition {
            description
                "The property definitions for the type of node or connection.";

            key "property-name";
            leaf property-name {
                description
                    "A user-visible and unique name for the property.";
                type nemo-common:property-name;
                mandatory true;
            }

            leaf property-value-type {
                description
                    "The type of the property value.";
                default string;
                type enumeration {
                    enum string {
                        description
                            "An string-valued property.";
                    }
                    enum int {
                        description
                            "An integer-valued property.";
                    }
                    enum range {
                        description
                            "An integer-range property.";
                    }
                }
            }

            leaf is-required {
                description
                    "Specify whether the property is required for the object.";
                default optional;
                type enumeration {
                    enum required {
                        description
                            "The property is required";
                    }
                    enum optional {
                        description
                            "The property is optional";
                    }
                }
            }

            leaf is-read-only {
                description
                    "Specify whether the property is read-only for object.";
                default write-read;
                type enumeration {
                    enum write-read {
                        description
                            "The property can be read and written.";
                    }
                    enum read-only {
                        description
                            "The property is read-only.";
                    }
                }
            }
        }
    }

    container node-definitions {
        list node-definition {
            description
                "Define new node model/type which can be used in other places,
                 and include node type name and its property.";

            key "node-type";
            leaf node-type {
                description
                    "A user-visible and unique identifier for the node type.";
                type nemo-common:node-type;
                mandatory true;
            }

            uses property-definitions;
        }
    }

    container connection-definitions {
        list connection-definition {
            description
                "Define new connection model/type which can be used in other places,
                 and include connection type name and its property.";

            key "connection-type";
            leaf connection-type {
                description
                    "A user-visible and unique identifier for the connection type.";
                type nemo-common:connection-type;
                mandatory true;
            }

            uses property-definitions;
        }
    }

    container match-item-definitions {
        list match-item-definition {
            description
                "Define the match item which uses to match the flow.";

            key "match-item-name";
            leaf match-item-name {
                description
                    "A user-visible and unique name for the match item.";
                type nemo-common:match-item-name;
                mandatory true;
            }

            leaf match-item-value-type {
                description
                    "The value type of the match item.";
                default string;
                type enumeration {
                    enum string {
                        description
                            "A string-valued match item.";
                    }
                    enum int {
                        description
                            "An integer-valued match item.";
                    }
                    enum range {
                        description
                            "An integer-range match item.";
                    }
                }
            }
        }
    }

    container flow-property-definitions {
        description
            "Contains the property definitions for the flow.";

        uses property-definitions;
    }

    container connection-point-definitions {
        list connection-point-definition {
            description
                "Define new connectionPoint model/type which can be used in other places,
                 and include the External Interface name from the VNFD .";
            key "vnfd-interface-name";
            leaf vnfd-interface-name {
                description
                    "A user-visible and unique identifier for the external Interface name associated with this connectionPoint .";
                type nemo-common:vnfd-interface-name;
            }
        
        }
    }

    grouping property-instance {
        description
            "The property instance and its associated metadata.";

        leaf property-name {
            description
                "The name for the property which can be seen as a unique
                 identifier of the property.";
            type nemo-common:property-name;
            mandatory true;
        }

        container property-values {
            description
                "The value list of the property.";

            list string-value {
                key "value order";
                leaf value {
                    type string;
                }

                leaf order {
                    type uint32;
                }
            }

            list int-value {
                key "value order";
                leaf value {
                    type int64;
                }

                leaf order {
                    type uint32;
                }
            }

            container range-value {
                leaf min {
                    type int64;
                    
                }

                leaf max {
                    type int64;
                    
                }
            }
        }
    }

    grouping node-instance {
        description
            "It represents the node instance and its metadata.
             A node represents the functions a network node may provide in a
             network such as network services,or a group of network elements.";

        leaf node-id {
            description
                "A unique ID for a node instance";
            type nemo-common:node-id;
            mandatory true;
        }

        leaf node-name {
            description
                "A user-visible and unique name for a node instance.";
            type nemo-common:node-name;
            mandatory true;
        }

        leaf node-type {
            description
                "A user-visible and unique type identifier for a node instance.";
            type nemo-common:node-type;
            mandatory true;
        }

        list sub-node {
            description
                "Represents the sub-nodes which have been included
                 by the node instance logically.";

            key "node-id";
            leaf node-id {
                description
                    "A unique ID for a node instance.";
                type nemo-common:node-id;
            }

            leaf order {
                description
                    "Specify the order of the node in a sequence node list.";
                type uint32;
            }
        }

        list property {
            description
                "The property list of a node instance.";

            key "property-name";
            uses property-instance;
        }
    }

    grouping connection-instance {
        description
            "It represents the connection instance and its metadata.
             The Connection describes the resource between node entities.
             This connection is not limited to any physical link, but just
             expresses the communication capacity between nodes.";

        leaf connection-id {
            description
                "A unique ID for a connection instance.";
            type nemo-common:connection-id;
            mandatory true;
        }

        leaf connection-name {
            description
                "A user-visible and unique name for a connection instance.";
            type nemo-common:connection-name;
            mandatory true;
        }

        leaf connection-type {
            description
                "A user-visible and unique type identifier for a connection instance.";
            type nemo-common:connection-type;
            mandatory true;
        }

        list end-node {
            description
                "Represents the nodes which will be connected by connection.
                 At least two nodes in the list.";

            key "node-id";
            leaf node-id {
                description
                    "A unique ID for a node instance.";
                type nemo-common:object-id;
            }

            leaf order {
                description
                    "Specify the order of the node in a sequence node list";
                type uint32;
            }

            min-elements 2;
        }

        list property {
            description
                "The property list of a connection instance.";

            key "property-name";
            uses property-instance;
        }
    }

    grouping match-item-instance {
        description
            "Represents the match item and its metadata.";

        leaf match-item-name {
            description
                "A name for a match item.";
            type nemo-common:match-item-name;
            mandatory true;
        }

        container match-item-value {
            description
                "The value of a match item.";

            leaf string-value {
                type string;
            }

            leaf int-value {
                type int64;
            }

            container range-value {
                leaf min {
                    type int64;
                    mandatory true;
                }

                leaf max {
                    type int64;
                    mandatory true;
                }
            }
        }
    }

    grouping flow-instance {
        description
            "Represents the flow instance and its metadata.
             The flow refers to the traffic in network which describes
             data packets have some certain characters.";

        leaf flow-id {
            description
                "A unique ID for a flow instance.";
            type nemo-common:flow-id;
            mandatory true;
        }

        leaf flow-name {
            description
                "A user-visible and unique name for a flow instance.";
            type nemo-common:flow-name;
            mandatory true;
        }

        list match-item {
            description
                "The match item list of a flow instance.";

            key "match-item-name";
            uses match-item-instance;
        }

        list property {
            description
                "The property list of a flow instance.";

            key "property-name";
            uses property-instance;
        }
    }

    grouping connection-point-instance {
        description
            "It represents the connectionPoint instance and its metadata.
             This ConnectionPoint can be the attachment point for the new VNF with either a virtual network interface defined in the VNFD or a connection.";

        leaf connection-point-id {
            description
                "A unique ID for a connectionPoint instance.";
            type nemo-common:connection-point-id;
            mandatory true;
        }

        leaf connection-point-name {
            description
                "A user-visible and unique name for a connectionPoint instance.";
            type nemo-common:connection-point-name;
            mandatory true;
        }

        leaf vnfd-interface-name {

            description
                "It represents de virtual network interface defined in the VNFD.";
            type nemo-common:vnfd-interface-name;
        }
    }

}
