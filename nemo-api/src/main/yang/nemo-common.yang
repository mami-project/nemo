/*
 * Copyright (c) 2015 Huawei, Inc. and others. All rights reserved.
 *
 * This program and the accompanying materials are made available under the
 * terms of the Eclipse Public License v1.0 which accompanies this distribution,
 * and is available at http://www.eclipse.org/legal/epl-v10.html
 */

module nemo-common {
    yang-version 1;

    namespace "urn:opendaylight:params:xml:ns:yang:nemo:common";
    prefix "nemo-common";

    description
        "Common types and definitions for NEMO models";

    revision "2015-10-10" {
        description
            "Initial revision.";
    }

    // *********************
    // * Base Types
    // *********************
    typedef description {
        description
            "A human-readable description for a object.";
        type string {
            length "1..4096";
        }
    }

    typedef name {
        description
            "A generic string name type. Must start with a letter";
        type string {
            pattern '[a-zA-Z]([a-zA-Z0-9\-_.])*';
            length "1..256";
        }
    }

    // UUID type from ietf-yang-types@2013-07-15
    typedef uuid {
        type string {
            pattern '[0-9a-fA-F]{8}-[0-9a-fA-F]{4}-[0-9a-fA-F]{4}-'
                + '[0-9a-fA-F]{4}-[0-9a-fA-F]{12}';
        }
        description
            "A Universally Unique IDentifier in the string representation
             defined in RFC 4122. The canonical representation uses
             lower case characters.

             The following is an example of a UUID in string
             representation: f81d4fae-7dec-11d0-a765-00a0c91e6bf6";
        reference
            "RFC 4122: A Universally Unique IDentifier (UUID) URN
             Namespace";
    }

    typedef unique-id {
        description
            "A globally unique identifier.";
        type uuid;
    }

    // *********************
    // * Unique IDs
    // *********************
    typedef object-id {
        description
            "A unique ID for a parameterized object.";
        type unique-id;
    }

    typedef node-id {
        description
            "A unique ID for a node.";
        type object-id;
    }

    typedef connection-id {
        description
            "A unique ID for a connection.";
        type object-id;
    }

    typedef connection-point-id {
        description
            "A unique ID for a connectionPoint.";
        type object-id;
    }

    typedef flow-id {
        description
            "A unique ID for a flow.";
        type object-id;
    }

    typedef intent-id {
        description
            "A unique ID for an intent.";
        type unique-id;
    }

    typedef user-id {
        description
            "A unique ID for a user.";
        type unique-id;
    }

    typedef operation-id {
        description
            "A unique ID for an operation.";
        type unique-id;
    }

    typedef condition-segment-id {
        description
            "A unique ID for a segment of the condition in an operation.";
        type unique-id;
    }

    typedef constraint-segment-id {
        description
            "A unique ID for a segment of the constraint in an operation.";
        type unique-id;
    }

    typedef query-condition-id {
        description
            "A unique ID for a condition of the advanced query.";
        type unique-id;
    }

    typedef template-instance-id {
        description
            "A unique ID for a template instance.";
        type unique-id;
    }

    // *********************
    // * Names
    // *********************
    typedef object-name {
        description
            "A name for a parameterized object";
        type name;
    }

    typedef node-name {
        description
            "A name for a node instance.";
        type object-name;
    }

    typedef connection-name {
        description
            "A name for a connection instance.";
        type object-name;
    }

    typedef connection-point-name {
        description
            "A name for a connectionPoint instance.";
        type object-name;
    }    

    typedef flow-name {
        description
            "A name for a flow instance.";
        type object-name;
    }

    typedef  match-item-name {
        description
            "A name for a match item.";
        type name;
    }

    typedef property-name {
        description
            "A name for a property.";
        type name;
    }

    typedef parameter-name {
        description
            "A name for a parameter.";
        type name;
    }

    typedef action-name {
        description
            "A name for an action.";
        type name;
    }

    typedef condition-parameter-name {
        description
            "A name for a parameter of condition.";
        type name;
    }

    typedef constraint-parameter-name {
        description
            "A name for a parameter of constraint.";
        type name;
    }

    typedef user-name {
        description
            "A name for a user.";
        type name;
    }

    typedef user-password {
        description
            "A password for a user.";
        type name;
    }

    typedef operation-name {
        description
            "A name for an operation.";
        type name;
    }

    typedef query-condition-name {
        description
            "A name for a query with condition.";
        type name;
    }

    typedef user-role-name {
        description
            "A role name for a user.";
        type name;
    }

    typedef user-role-description {
        description
            "It describes the role characteristic and responsibility range.";
        type string;
    }

    typedef template-name {
        description
            "A unique name for a template";
        type name;
    }

    typedef template-instance-name {
        description
            "A unique name for a template instance.";
        type name;
    }

    typedef vnfd-interface-name {
        description
            "A unique name for a interface defined by VNF Descriptor.";
        type name;
    }
    

    // *********************
    // * Types
    // *********************
    typedef node-type {
        description
            "The type for a node.";
        type name;
    }

    typedef connection-type {
        description
            "The type for a connection.";
        type name;
    }

    typedef flow-type {
        description
            "The type for a flow.";
        type name;
    }

    typedef connection-point-type {
        description
            "The type for a connectionPoint.";
        type name;
    }   
}
